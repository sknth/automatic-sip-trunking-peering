module ietf-sip-auto-peering {
      namespace "urn:ietf:params:xml:ns:ietf-sip-auto-peering";
      prefix "peering";

      import ietf-inet-types {
        prefix "inet";
      }

      description
      "Data model for encoding SIP Service Provider Capability Set";

      revision 2022-12-26 {
        description "Capability set document v2";
      }

      typedef ipv4-address-port {
        type string {
          pattern "(([0-9]|[1-9][0-9]|1[0-9][0-9]|2[0-4][0-9]|25[0-5])"
          + "\.){3}([0-9]|[1-9][0-9]|1[0-9][0-9]|2[0-4][0-9]|25[0-5])"
          + ":^()([1-9]|[1-5]?[0-9]{2,4}|6[1-4][0-9]{3}|65[1-4][0-9]"
          + "{2}|655[1-2][0-9]|6553[1-5])$";
        }
        description "The ipv4-address-port type represents an IPv4
        address in dotted-quad notation followed by a port number.";
      }

      typedef ipv6-address-port {
        type string {
          pattern "((:|[0-9a-fA-F]{0,4}):)([0-9a-fA-F]{0,4}:){0,5}"
          + "((([0-9a-fA-F]{0,4}:)?(:|[0-9a-fA-F]{0,4}))|"
          + "(((25[0-5]|2[0-4][0-9]|[01]?[0-9]?[0-9])\.){3}"
          + "(25[0-5]|2[0-4][0-9]|[01]?[0-9]?[0-9])))"
          + ":^()([1-9]|[1-5]?[0-9]{2,4}|6[1-4][0-9]{3}|65[1-4][0-9]"
          + "{2}|655[1-2][0-9]|6553[1-5])$";
          pattern
          "(([^:]+:){6}(([^:]+:[^:]+)|(.*\..*)))|"
          + "((([^:]+:)*[^:]+)?::(([^:]+:)*[^:]+)?)"
          + ":^()([1-9]|[1-5]?[0-9]{2,4}|6[1-4][0-9]{3}|65[1-4][0-9]"
          + "{2}|655[1-2][0-9]|6553[1-5])$";
        }
          description
          "The ipv6-address type represents an IPv6 address in full,
          mixed, shortened, and shortened-mixed notation followed by
          a port number.";
      }

      typedef ip-address-port {
        type union {
          type ipv4-address-port;
          type ipv6-address-port;
        }
        description
        "The ip-address-port type represents an IP address:port number
        and is IP version neutral.";
      }

      typedef domain-name-port {
        type string {
          pattern
          "((([a-zA-Z0-9_]([a-zA-Z0-9\-_]){0,61})?[a-zA-Z0-9]\.)*"
          + "([a-zA-Z0-9_]([a-zA-Z0-9\-_]){0,61})?[a-zA-Z0-9]\.?)"
          + "|\."
          + ":^()([1-9]|[1-5]?[0-9]{2,4}|6[1-4][0-9]{3}|65[1-4][0-9]"
          + "{2}655[1-2][0-9]|6553[1-5])$";
          length "1..258";
        }
        description
        "The domain-name-port type represents a DNS domain name
        followed by a port number. The name SHOULD be fully qualified
        whenever possible.";
      }

      typedef host-port {
        type union {
          type ip-address-port;
          type domain-name-port;
        }
        description
        "The host type represents either an IP address or a DNS
        domain name followed by a port number.";
      }

      container peering-info {
        leaf variant {
          type string;
          mandatory true;
          description "Variant of peering-response document";
        }

        container revision {
          leaf notBefore {
              type string;
              mandatory true;
              description "Time and date specifying when the
            parameters specified in this capability set document are considered
            active or valid";
          }

          leaf location {
              type string;
              mandatory true;
              description "Location of the new version of
              capability set document";
          }
        }

        container transport-info {
          leaf transport {
            type enumeration {
              enum "TCP";
              enum "TLS";
              enum "UDP";
              enum "TCP;TLS";
              enum "TCP;TLS;UDP";
              enum "TCP;UDP";
            }
            mandatory true;
            description "Transport Protocol(s) used in SIP
            communication";
          }

          leaf-list registrar {
            type host-port;
            max-elements 3;
            description "List of service provider registrar servers";
          }

          list realms {
            key "name";
            leaf name {
              type string;
              mandatory true;
              description "Name of the realm or protection domain in the
              service provider network";
            }

            leaf username {
              type string;
              description "Username for digest authentication within the
              realm specified in the preceding leaf";
            }

            leaf password {
              type string;
              description "Password for digest authentication within the
              realm specified in the preceding leaf";
            }
          }

          leaf-list callControl {
            type host-port;
            max-elements 3;
            description "List of service provider call control
            servers";
          }

          leaf-list dns {
            type inet:ip-address;
            max-elements 2;
            description "IP address of the DNS Server(s) hosted by the
            service provider";
          }

          leaf outboundProxy {
            type host-port;
            description "SIP Outbound Proxy";
          }
        }

        container call-specs {
          leaf earlyMedia {
            type boolean;
            description "Flag indicating whether the service provider
            is expected to deliver early media.";
          }

          leaf signalingForking {
            type boolean;
            description "Flag indicating if the service provider may
            fork calls made from the enterprise network";
          }

          leaf supportedMethods {
            type string;
            description "Leaf/Leaf List indicating the different SIP
            methods supported by the service provider.";
          }

          container callerId {
            leaf e164Format {
              type boolean;
              description "Flag indicating whether the enterprise must
              format calling numbers in E.164 format";
            }

            leaf preferredMethod {
              type string;
              description "Field specifying which SIP header must be used
              by the enterprise network to communicate caller information";
            }
          }

          container numRange {
            leaf numRangeType {
              type string;
              description "String indicating whether the number range allocated
              to the enterprise network is passed by value or by reference";
            }

            leaf count {
              when "../numRangeType = 'range' or
              ../numRangeType = 'collection'";
              type int32;
              description "The count of the individual numbers present in the
              number range.";
            }

            leaf-list value {
              type string;
              description "Value of the individual number in the number range
              or URL being passed as reference";
            }

          }
        }

        container media {
          container mediaTypeAudio {
            leaf-list mediaFormat {
              type string;
              description "Leaf List indicating the audio media formats
              supported by the service provider";
            }
          }

          container fax {
            leaf-list protocol {
              type enumeration {
                enum "pass-through";
                enum "t38";
              }
              max-elements 2;
              description "Leaf List indicating the different fax
              protocols supported by the service provider.";
            }
          }

          container rtp {
            leaf RTPTrigger {
              type boolean;
              description "Flag indicating whether the service provider
              expects to receive the first media packet from the enterprise
              network in a connected SIP session";
            }

            leaf symmetricRTP {
              type boolean;
              description "Flag indicating whether the service provider
              expects symmetric RTP defined in [@RFC4961]";
            }
          }

          container rtcp {
            leaf symmetricRTCP {
              type boolean;
              description "Flag indicating whether the service
              provider expects symmetric RTP defined in [@RFC4961].";
            }

            leaf RTCPfeedback {
              type boolean;
              description "Flag Indicating support for RTP profile
              extension for RTCP-based feedback, as defined in
              [@RFC4585]";
            }
          }
        }

        container dtmf {
          leaf payloadNumber {
            type int8 {
              range "96..127";
            }
            description "Leaf indicating the payload number(s) supported by
            the service provider for DTMF related via RTP NTE";
          }

          leaf iteration {
            type boolean;
            description "Flag identifying whether the service provider
            supports RTP-NTE DTMF relay using the procedures of [@RFC2833]
            or [@RFC4733] .";
          }
        }

        container security {
          container signaling {
            leaf secure {
              type boolean;
              description "Flag indicating whether the service provider
              supports SIP over TLS";
            }

            leaf version {
              type string {
                pattern "([1-9]\.[0-9])(;[1-9]\.[0-9])?|(NULL)";
              }
              description "Leaf indicating the TLS version supported by the
              SIP service provider";
            }
          }

          container mediaSecurity {
            leaf keyManagement {
              type string {
                pattern "(SDES(;DTLS-SRTP,version=[1-9]\.[0-9](,[1-9]"
                + "\.[0-9])?)?)|(DTLS-SRTP,version=[1-9]\.[0-9](,[1-9]"
                + "\.[0-9])?)|(NULL)";
              }
              description "Leaf indicating the key management
              methods supported by the service provider for SRTP.";
            }
          }

          leaf certLocation {
            type string;
            description "Location of the service provider certificate
            chain for SIP over TLS.";
          }

          container secureTelephonyIdentity {
            leaf STIRCompliance {
              type boolean;
              description "Indicates whether the SIP service provider
              is STIR compliant.";
            }

            leaf certDelegation {
              type boolean;
              description "Indicates whether a SIP service provider is
              willing to delegate authority to the enterprise network
              over its allocated number range(s)";
            }

            leaf ACMEDirectory {
              when "../certDelegation = 1 or ../certDelegation = 'true'";
              type string;
              description "Directory object URL, when de-referenced,
              provides a collection of field name-value pairs to
              kickstart ACME.";
            }
          }
        }

        leaf extensions {
          type string;
          description "Lists the various SIP extensions supported by
          the service provider.";
        }
      }
    }
