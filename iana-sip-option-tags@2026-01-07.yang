module iana-sip-option-tags {
  yang-version 1.1;
  namespace "urn:ietf:params:xml:ns:yang:iana-sip-option-tags";
  prefix iana-sip-option-tags;

  organization
    "Internet Assigned Numbers Authority (IANA)";

  contact
    "Internet Assigned Numbers Authority

     ICANN
     12025 Waterfront Drive, Suite 300
     Los Angeles, CA 90094

     Tel: +1 424 254 5300

     <mailto:iana@iana.org>";

  description
    "This YANG module translates IANA registry SIP 'Option Tags'
     to YANG derived types.

     Copyright (c) 2025 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     The initial version of this YANG module is part of RFC XXXX;
     see the RFC itself for full legal notices.

     The latest version of this YANG module is available at
     <IANA_URL>.
     
     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  reference
    "RFC XXXX";

  revision 2026-01-07 {
    description
      "Initial revision.";
    reference
      "NOTE TO RFC EDITOR: Please replace 'RFC XXXX' with the actual
      RFC number of this document when published, and delete this
      sentence. Also replace the revision with the date of publication
      of this document.
      RFC XXXX: Automatic Peering for SIP Trunks";
  }

  typedef sip-option-tag {
    type enumeration {
      enum one-hundred-rel {
        description
          "This option tag is for reliability of provisional
          responses. When present in a Supported header, it
          indicates that the UA can send or receive reliable
          provisional responses. When present in a Require header
          in a request it indicates that the UAS MUST send all
          provisional responses reliably. When present in a Require
          header in a reliable provisional response, it indicates
          that the response is to be sent reliably.";
        reference
          "RFC 3262: Reliability of Provisional Responses in the
          Session Initiation Protocol (SIP).";
      }

      enum one-nine-nine {
        description
          "This option-tag is for indicating support of the 199 Early
          Dialog Terminated provisional response code. When present
          in a Supported header of a request, it indicates that the
          UAC supports the 199 response code. When present in a Require
          or Proxy-Require header field of a request, it indicates that
          the UAS, or proxies, MUST support the 199 response code. It
          does not require the UAS, or proxies, to actually
          send 199 responses.";
        reference
          "RFC 6228: Session Initiation Protocol (SIP) Response Code
          for Indication of Terminated Dialog.";
      }

      enum answermode {
        description
          "This option tag is for support of the Answer-Mode
           and Priv-Answer-Mode extensions used to negotiate
           automatic or manual answering of a request.";
        reference
          "RFC 5373: Requesting Answering Modes for the Session 
          Initiation Protocol (SIP).";
      }

      enum early-session {
        description
          "A UA adding the early-session option tag to a message
           indicates that it understands the early-session content
           disposition.";
        reference
          "RFC 3959: The Early Session Disposition Type for the Session
          Initiation Protocol (SIP).";
      }

      enum eventlist {
        description
          "Extension to allow subscriptions to lists of resources.";
        reference
          "RFC 4662: A Session Initiation Protocol (SIP) Event
          Notification Extension for Resource Lists.";
      }

      enum explicitsub {
        description
          "This option tag identifies an extension to REFER to
           suppress the implicit subscription and provide a URI
           for an explicit subscription.";
        reference
          "RFC 7614: Explicit Subscriptions for the REFER Method.";
      }

      enum from-change {
        description
          "This option tag is used to indicate that a UA supports
           changes to URIs in From and To header fields during a
           dialog.";
        reference
          "RFC 4916: Connected Identity in the Session Initiation
          Protocol (SIP).";
      }

      enum geolocation-http {
        description
          "The geolocation-http option tag signals support for
           acquiring location information via HTTP. A location
           recipient who supports this option can request location
           with an HTTP GET and parse a resulting 200 response
           containing a PIDF-LO object. The URI schemes supported
           by this option include http and https.";
        reference
          "RFC 6442: Location Conveyance for the Session Initiation
          Protocol.";
      }

      enum geolocation-sip {
        description
          "The geolocation-sip option tag signals support for
           acquiring location information via the presence event
           package of SIP. A location recipient who supports this
           option can send a SUBSCRIBE request and parse a
           resulting NOTIFY containing a PIDF-LO object. The URI
           schemes supported by this option include sip, sips, and
           pres.";
        reference
          "RFC 6442: Location Conveyance for the Session Initiation
          Protocol.";
      }

      enum gin {
        description
          "This option tag is used to identify the extension that
           provides Registration for Multiple Phone Numbers in
           SIP. When present in a Require or Proxy-Require header
           field of a REGISTER request, it indicates that support
           for this extension is required of registrars and
           proxies that are a party to the registration
           transaction.";
        reference
          "RFC 6140: Registration for Multiple Phone Numbers in the
          Session Initiation Protocol (SIP).";
      }

      enum gruu {
        description
          "This option tag is used to identify the Globally
           Routable User Agent URI extension. When used in a
           Supported header, it indicates that a User Agent
           understands the extension. When used in a Require
           header field of a REGISTER request, it indicates that
           the registrar is not expected to process the
           registration unless it supports the extension.";
        reference
          "RFC 5627: Obtaining and Using Globally Routable User Agent
          URIs (GRUUs) in the Session Initiation Protocol (SIP).";
      }

      enum histinfo {
        description
          "When used with the Supported header field, this option
           tag indicates the UAC supports History Information to
           be captured for requests and returned in subsequent
           responses. This tag is not used in a Proxy-Require or
           Require header field, since support of History-Info is
           optional.";
        reference
          "RFC 7044: An Extension to the Session Initiation Protocol
          (SIP) for Request History Information.";
      }

      enum ice {
        description
          "This option tag is used to identify the Interactive
           Connectivity Establishment extension. When present in
           a Require header field, it indicates that ICE is
           required by an agent.";
        reference
          "RFC 5768: Indicating Support for Interactive Connectivity
          Establishment (ICE) in the Session Initiation Protocol
          (SIP).";
      }

      enum join {
        description
          "Support for the SIP Join header.";
        reference
          "RFC 3911: The Session Initiation Protocol (SIP) 'Join'
          Header.";
      }

      enum multiple-refer {
        description
          "This option tag indicates support for REFER requests
           that contain a resource list document describing
           multiple REFER targets.";
        reference
          "RFC 5368: Referring to Multiple Resources in the Session
          Initiation Protocol (SIP).";
      }

      enum norefersub {
        description
          "This option tag specifies a User Agent ability of
           accepting a REFER request without establishing an
           implicit subscription compared to the default case.";
        reference
          "RFC 4488: Suppression of Session Initiation Protocol (SIP)
          REFER Method Implicit Subscription.";
      }

      enum nosub {
        description
          "This option tag identifies an extension to REFER to
           suppress the implicit subscription and indicate that
           no explicit subscription is forthcoming.";
        reference
          "RFC 7614: Explicit Subscriptions for the REFER Method.";
      }

      enum outbound {
        description
          "This option tag is used to identify UAs and Registrars
           which support extensions for Client Initiated
           Connections. A UA places this option tag in a Supported
           header to communicate its support. A Registrar places
           this option tag in a Require header to indicate that
           the Registrar used registrations based on this
           extension.";
        reference
          "RFC 5626: Managing Client-Initiated Connections in the
          Session Initiation Protocol (SIP).";
      }

      enum path {
        description
          "A SIP UA that supports the Path extension header field
           includes this option tag in a Supported header field in
           all requests it generates. Intermediate proxies may
           use this option tag in a REGISTER request to determine
           whether to offer Path service. If required, the option
           tag is included in a Require header field.";
        reference
          "RFC 3327: Session Initiation Protocol (SIP) Extension Header
          Field for Registering Non-Adjacent Contacts.";
      }

      enum policy {
        description
          "This option tag is used to indicate that a UA can
           process policy server URIs and subscribe to
           session-specific policies.";
        reference
          "RFC 6794: A Framework for Session Initiation Protocol (SIP)
          Session Policies.";
      }

      enum precondition {
        description
          "An offerer MUST include this tag in the Require header
           field if the offer contains one or more mandatory
           strength-tags. If all strength-tags are optional or
           none, the tag MUST be included in Supported or
           Require.";
        reference
          "RFC 3312: Integration of Resource Management and Session
          Initiation Protocol (SIP).";
      }

      enum pref {
        description
          "This option tag is used to ensure that a server
           understands the callee capabilities parameters used in
           the request.";
        reference
          "RFC 3840: Indicating User Agent Capabilities in the Session
          Initiation Protocol (SIP).";
      }

      enum privacy {
        description
          "This option tag indicates support for the Privacy
           mechanism. When used in the Proxy-Require header, it
           indicates that proxy servers do not forward the
           request unless they can provide the requested privacy
           service. Proxies remove this option tag after the
           privacy function has been performed.";
        reference
          "RFC 3323: A Privacy Mechanism for the Session Initiation
          Protocol (SIP).";
      }

      enum recipient-list-invite {
        description
          "The body contains a list of URIs that indicates the
           recipients of the SIP INVITE request.";
        reference
          "RFC 5366: Conference Establishment Using Request-Contained
          Lists in the Session Initiation Protocol (SIP).";
      }

      enum recipient-list-message {
        description
          "The body contains a list of URIs that indicates the
           recipients of the SIP MESSAGE request.";
        reference
          "RFC 5365: Multiple-Recipient MESSAGE Requests in the Session
          Initiation Protocol (SIP).";
      }

      enum recipient-list-subscribe {
        description
          "This option tag is used to ensure that a server can
           process the recipient-list body used in a SUBSCRIBE
           request.";
        reference
          "RFC 5367: Subscriptions to Request-Contained Resource Lists
          in the Session Initiation Protocol (SIP).";
      }

      enum record-aware {
        description
          "This option tag indicates the ability of the UA to
           receive recording indicators in media-level or
           session-level SDP. When present in a Supported header,
           it indicates that the UA can receive such indicators.";
        reference
          "RFC 7866: Session Recording Protocol.";
      }

      enum replaces {
        description
          "This option tag indicates support for the SIP Replaces
           header.";
        reference
          "RFC 3891: The Session Initiation Protocol (SIP) 'Replaces'
          Header.";
      }

      enum resource-priority {
        description
          "Indicates or requests support for the resource
           priority mechanism.";
        reference
          "RFC 4412: Communications Resource Priority for the Session
          Initiation Protocol (SIP).";
      }

      enum sdp-anat {
        description
          "The sdp-anat option tag is defined for use in Require
           and Supported SIP header fields. User agents that place
           this option tag in a Supported header understand the
           ANAT semantics.";
        reference
          "RFC 4092: Usage of the Session Description Protocol (SDP)
          Alternative Network Address Types (ANAT) Semantics in the
          Session Initiation Protocol (SIP).";
      }

      enum sec-agree {
        description
          "This option tag indicates support for the Security
           Agreement mechanism. When used in Require or
           Proxy-Require headers, it indicates proxies are
           required to use the mechanism. When used in Supported,
           it indicates UAC support. When used in Require headers
           in responses, it indicates mandatory use.";
        reference
          "RFC 3329: Security Mechanism Agreement for the Session
          Initiation Protocol (SIP).";
      }

      enum siprec {
        description
          "This option tag identifies that the SIP session is for
           the purpose of a recording session. When present in a
           Require header, it indicates that the UA is capable of
           handling such a session.";
        reference
          "RFC 7866: Session Recording Protocol.";
      }

      enum tdialog {
        description
          "This option tag identifies the Target-Dialog header
           field extension. When used in Require, the recipient
           must support it. When used in Supported, the sender
           supports it.";
        reference
          "RFC 4538: Request Authorization through Dialog Identification
          in the Session Initiation Protocol (SIP).";
      }

      enum timer {
        description
          "This option tag indicates support for the session timer
           extension. Inclusion in Supported indicates refresh
           capability. Inclusion in Require indicates mandatory
           support for processing.";
        reference
          "RFC 4028: Session Timers in the Session Initiation Protocol
          (SIP).";
      }

      enum trickle-ice {
        description
          "This option tag indicates that a UA supports and
           understands Trickle ICE.";
        reference
          "RFC 8840: A Session Initiation Protocol (SIP) Usage for
          Incremental Provisioning of Candidates for the Interactive
          Connectivity Establishment (Trickle ICE).";
      }

      enum uui {
        description
          "This option tag indicates that a UA supports and
           understands the User-to-User header field.";
        reference
          "RFC 7433: A Mechanism for Transporting User-to-User Call
          Control Information in SIP.";
      }
    }
    description
      "This enumeration type defines mnemonic names of SIP Option
       tags.";
    reference
      "RFC 3261: SIP: Session Initiation Protocol,
       RFC 5727: Change Process for the Session Initiation
                 Protocol (SIP) and the Real-time Applications
                 and Infrastructure Area";
  }
}
